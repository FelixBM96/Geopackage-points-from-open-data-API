FME workspace FME_TEST_3.fmw

Parameters:
- DestDataset_OGCGEOPACKAGE =

Writers:
- OGCGEOPACKAGE_1: OGCGEOPACKAGE to $(DestDataset_OGCGEOPACKAGE) in EPSG:3006

Note: Gather data from API. 4 callers because size of result window is 500 from API.
Note: Fragments data. Documentation or separate JSONFragmenter shows i need "results". json["results"][*]
Creator
    GEOMTYPE = Geometry Object
    NUM = 1
    CREATED -> HTTPCaller
    CREATED -> HTTPCaller_2
    CREATED -> HTTPCaller_3
    CREATED -> HTTPCaller_4

Bookmark: Gather data from API
HTTPCaller
    ADDITIONAL_URL_PARAMETERS = _limit;500 _offset;0
    CONNECTION_TIMEOUT_LENGTH = 60
    CUSTOM_HEADERS = Accept;application/json
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://vgregion.entryscape.net/rowstore/dataset/3d6b77d0-4557-4c82-9d24-e2bd22d4d090
    TRANSFER_TIMEOUT_LENGTH = 90
    USE_COOKIES = No
    VERIFY_SSL_CERTIFICATES = Yes
    -> JSONFragmenter
HTTPCaller_2
    ADDITIONAL_URL_PARAMETERS = _limit;500 _offset;500
    CONNECTION_TIMEOUT_LENGTH = 60
    CUSTOM_HEADERS = Accept;application/json
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://vgregion.entryscape.net/rowstore/dataset/3d6b77d0-4557-4c82-9d24-e2bd22d4d090
    TRANSFER_TIMEOUT_LENGTH = 90
    USE_COOKIES = No
    VERIFY_SSL_CERTIFICATES = Yes
    -> JSONFragmenter
HTTPCaller_3
    ADDITIONAL_URL_PARAMETERS = _limit;500 _offset;1000
    CONNECTION_TIMEOUT_LENGTH = 60
    CUSTOM_HEADERS = Accept;application/json
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://vgregion.entryscape.net/rowstore/dataset/3d6b77d0-4557-4c82-9d24-e2bd22d4d090
    TRANSFER_TIMEOUT_LENGTH = 90
    USE_COOKIES = No
    VERIFY_SSL_CERTIFICATES = Yes
    -> JSONFragmenter
HTTPCaller_4
    ADDITIONAL_URL_PARAMETERS = _limit;500 _offset;1500
    CONNECTION_TIMEOUT_LENGTH = 60
    CUSTOM_HEADERS = Accept;application/json
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://vgregion.entryscape.net/rowstore/dataset/3d6b77d0-4557-4c82-9d24-e2bd22d4d090
    TRANSFER_TIMEOUT_LENGTH = 90
    USE_COOKIES = No
    VERIFY_SSL_CERTIFICATES = Yes
    -> JSONFragmenter

Bookmark: Fragments data
JSONFragmenter
    EXPLODE_FORMAT = JSON
    EXTRACT_ATTR = No
    JSON_ATTR = _response_body
    JSON_QUERY = json["results"][*]
    READ_FROM_FILE = NO
    REJECT_EMPTY_LISTS = YES
    FRAGMENTS -> JSONFlattener

Bookmark: Expose attributes
JSONFlattener
    ERROR_LIST_ATTR = _json_error
    JSON_DOCUMENT = @Value(_response_body)
    NEW_ATTRIBUTES = besoksadress postnr ykoord id xkoord foretagsnamn url foretagskategori postort
    READ_FROM_FILE = NO
    RECURSIVE = Yes
    -> AttributeManager

Bookmark: Sort and delete attributes
AttributeManager
    ATTR_TABLE:
      REMOVE _creation_instance
      REMOVE _response_body
      REMOVE _http_status_code
      REMOVE json_type
      REMOVE json_index
      RENAME_SET_VALUE xkoord > ykoordinat = @Value(ykoordinat)
      RENAME_SET_VALUE ykoord > xkoordinat = @Value(xkoordinat)
    -> Sorter
Sorter
    SORT_PARM = id NUMERIC ASCENDING
    SORTED -> Table1 (writer OGCGEOPACKAGE_1)

Bookmark: Write to Geopackage
Table1 (writer OGCGEOPACKAGE_1)
    attributes: id text, foretagsnamn text, besoksadress text, postnr text, postort text, url text, foretagskategori text, ykoordinat text, xkoordinat text
