FME workspace FME_API_Vardcentraler.fmw

Parameters:
- DestDataset_OGCGEOPACKAGE =

Writers:
- OGCGEOPACKAGE_1: OGCGEOPACKAGE to $(DestDataset_OGCGEOPACKAGE) in EPSG:3006

Note: Limit needs to be greater than 212 to account for all records in results tab
Note: Fragments data. Documentation or separate JSONFragmenter shows i need "results". json["results"][*]
Creator
    GEOMTYPE = Geometry Object
    NUM = 1
    CREATED -> HTTPCaller

Bookmark: Gather data from API
HTTPCaller
    ADDITIONAL_URL_PARAMETERS = _limit;500 _offset;0
    CONNECTION_TIMEOUT_LENGTH = 60
    CUSTOM_HEADERS = Accept;application/json
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://vgregion.entryscape.net/rowstore/dataset/70241cef-e111-4b07-bb55-99b5981f47de
    TRANSFER_TIMEOUT_LENGTH = 90
    USE_COOKIES = No
    VERIFY_SSL_CERTIFICATES = Yes
    -> JSONFragmenter

Bookmark: Fragments data
JSONFragmenter
    EXPLODE_FORMAT = JSON
    EXTRACT_ATTR = No
    JSON_ATTR = _response_body
    JSON_QUERY = json["results"][*]
    READ_FROM_FILE = NO
    REJECT_EMPTY_LISTS = YES
    FRAGMENTS -> JSONFlattener

Bookmark: Exposes attributes
JSONFlattener
    ERROR_LIST_ATTR = _json_error
    JSON_DOCUMENT = @Value(_response_body)
    NEW_ATTRIBUTES = postnummer foretag ykoord id xkoord adress hsaid postort namn
    READ_FROM_FILE = NO
    RECURSIVE = Yes
    -> AttributeManager

Bookmark: Sort, delete and rename attributes
AttributeManager
    ATTR_TABLE:
      REMOVE _creation_instance
      REMOVE _response_body
      REMOVE _http_status_code
      REMOVE json_type
      REMOVE json_index
      RENAME_SET_VALUE foretag > foretagsnamn
      RENAME_SET_VALUE xkoord > ykoordinat = @Value(ykoordinat)
      RENAME_SET_VALUE ykoord > xkoordinat = @Value(xkoordinat)
    -> Sorter
Sorter
    SORT_PARM = id NUMERIC ASCENDING
    SORTED -> VC_API (writer OGCGEOPACKAGE_1)

Bookmark: Write to Geopackage
VC_API (writer OGCGEOPACKAGE_1)
    attributes: id text, namn text, foretagsnamn text, adress text, postnummer text, postort text, ykoordinat text, xkoordinat text, hsaid text
